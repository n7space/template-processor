Harness-Datamodel DEFINITIONS ::=
BEGIN
--  This file was generated automatically by OpenGEODE
IMPORTS
   CounterValue FROM SDL-PROJECT-DATAVIEW
   T-Int32, T-UInt32, T-Int8, T-UInt8, T-Boolean, T-Null-Record, T-Runtime-Error FROM TASTE-BasicTypes
   PID-Range, PID FROM System-Dataview;

Harness-States ::= ENUMERATED {wait}

Harness-Context ::= SEQUENCE {
   state Harness-States,
   init-done BOOLEAN,
   sender PID,
   offspring PID,
   x CounterValue
}

Harness-T-Runtime-Error-Selection ::= ENUMERATED {noerror-present(1), encodeerror-present(2), decodeerror-present(3)}
END
